module example-adm {
  yang-version 1.1;
  namespace "ari://example/adm/";
  prefix example-adm;

  import ietf-amm {
    prefix amm;
  }

  organization
    "Example Org." {
    amm:enum 65535;
  }
  contact
    "Some User <user@example.org>";
  description
    "Example ADM module with YANG syntax.
     The organization name and enumeration are IANA reserved.";
  reference
    "draft-ietf-dtn-adm-yang";

  revision 2025-01-31 {
    description
      "Updated for latest ADM document.";
    reference
      "draft-ietf-dtn-adm-yang";
  }
  amm:enum 1;
}
